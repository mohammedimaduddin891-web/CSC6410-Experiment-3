module student-host {
  yang-version 1.1;
  namespace "urn:example:csc6410:student-host";
  prefix sh;

  organization
    "CSC 6410 Week 3 experiment (teaching model)";
  description
    "The network configuration of one student computer.
     host_schema.json is the same model written as JSON Schema.";

  revision 2026-11-06 {
    description
      "Experiment 3.";
  }

  container host {
    leaf hostname {
      type string {
        length "1..253";
      }
      mandatory true;
    }
    leaf os {
      type enumeration {
        enum windows;
        enum macos;
        enum linux;
      }
      mandatory true;
    }
    leaf collected-at {
      type string;
      description
        "Time of collection, ISO 8601, e.g. 2026-11-07T19:40:00-06:00.";
    }
    leaf default-gateway {
      type string {
        pattern '(\d{1,3}\.){3}\d{1,3}';
      }
    }
    leaf-list dns-server {
      type string;
    }
    list interface {
      key "name";
      leaf name {
        type string {
          length "1..64";
        }
      }
      leaf type {
        type enumeration {
          enum ethernet;
          enum wifi;
          enum loopback;
          enum virtual;
          enum other;
        }
      }
      leaf mac {
        type string {
          pattern '[0-9a-f]{2}(:[0-9a-f]{2}){5}';
        }
        description
          "Lower case, colon separated.";
      }
      leaf oper-status {
        type enumeration {
          enum up;
          enum down;
        }
        mandatory true;
      }
      leaf mtu {
        type uint32 {
          range "68..65536";
        }
      }
      leaf-list ipv4 {
        type string {
          pattern '(\d{1,3}\.){3}\d{1,3}/\d{1,2}';
        }
      }
      leaf-list ipv6 {
        type string;
      }
    }
  }
}
